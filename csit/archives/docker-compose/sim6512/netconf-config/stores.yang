module stores {

    yang-version 1.1;

    namespace "org:onap:ccsdk:sample";

    prefix book-store;

	import ietf-yang-types { prefix yang; }
	import ietf-inet-types { prefix inet; }

    revision "2020-09-15" {
        description
        "Sample Model";
    }

    typedef year {
        type uint16 {
            range "1000..9999";
        }
    }

    container bookstore {

        leaf bookstore-name {
            type string;
        }

		list categories {

			key "code";

			leaf code {
				type string;
			}

			leaf name {
				type string;
			}

			list books {
				key title;

				leaf title {
					type string;
				}
				leaf lang {
					type string;
				}
				leaf-list authors {
					type string;
				}
				leaf pub_year {
					type year;
				}
				leaf price {
					type uint64;
				}
			}
		}
	}
}
