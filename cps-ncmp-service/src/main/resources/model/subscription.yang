module subscription {
    yang-version 1.1;
    namespace "org:onap:ncmp:subscription";

    prefix subs;

    revision "2023-03-21" {
        description
            "NCMP subscription model";
    }

    container subscription-registry {
        list subscription {
            key "clientID subscriptionName";

            leaf clientID {
                type string;
            }

            leaf subscriptionName {
                type string;
            }

            leaf topic {
                type string;
            }

            leaf isTagged {
                type boolean;
            }

            container predicates {

                list targetCmHandles {
                    key "cmHandleId";

                    leaf cmHandleId {
                      type string;
                    }

                    leaf status {
                      type string;
                    }

                    leaf details {
                        type string;
                    }
                }

                leaf datastore {
                    type string;
                }
            }

        }
    }
}
