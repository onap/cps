module cps-data-job-subscriptions {
    yang-version 1.1;
    namespace "org:onap:cps:ncmp";

    prefix cps-djs;

    revision "2025-09-03" {
        description
            "First release of cm data job (notification) subscriptions model";
    }

    container dataJob {
        list subscription {
            key "dataNodeSelector";
            leaf dataNodeSelector { type string; }
            leaf-list dataJobId { type string; }
            leaf status { type string; }
        }
    }
}
