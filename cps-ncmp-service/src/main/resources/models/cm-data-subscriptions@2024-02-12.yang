module cm-data-subscriptions {
  yang-version 1.1;
  namespace "org:onap:cps:ncmp";

  prefix cmds;

  revision "2024-02-12" {
    description
      "First release of cm data (notification) subscriptions model";
  }

  container datastores {

    list datastore {
      key "name";

      leaf name {
        type string;
      }

      container cm-handles {

        list cm-handle {
          key "id";

          leaf id {
            type string;
          }

          container filters {

            list filter {
              key "xpath";

              leaf xpath {
                type string;
              }

              leaf-list subscriptionIds {
                type string;
              }

            }
          }
        }
      }
    }
  }
}
