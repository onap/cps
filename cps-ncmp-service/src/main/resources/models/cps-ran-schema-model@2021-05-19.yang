module cps-ran-schema-model {
  yang-version 1.1;
  namespace "org:onap:ccsdk:features:sdnr:northbound:cps-ran-schema-model";
  prefix rn;

  revision 2021-05-19 {
    description
      "Initial Cps Model Schema";
  }

  revision 2021-01-28 {
    description
      "Initial Cps Model Schema";
  }

  typedef RegionId {
    type union {
      type uint8;
      type string {
        length 8;
      }
    }
    reference "similar to clause 2.10.1 of 3GPP TS 23.003";
  }


  // container for RAN Network

  container cps-ran-schema {
    list Regions {
      key "regionId"; // list Regions
      description
        "A list of regions in the RAN network to map to mutually exclusive NRCellCU's";
      leaf regionId {
        type RegionId;
      }
    }
  }
}
