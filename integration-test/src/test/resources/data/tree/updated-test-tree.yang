module test-tree {
    yang-version 1.1;

    namespace "org:onap:cps:test:test-tree";
    prefix tree;

    revision "2023-08-17" {
        description
            "added list of birds to nest";
    }

    revision "2020-09-15" {
        description
            "Sample Model";
    }

    container test-tree {
        list branch {
            key "name";
            leaf name {
                type string;
            }
            container nest {
                leaf name {
                    type string;
                }
                leaf-list birds {
                    type string;
                }
            }
        }
    }
}
