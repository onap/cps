module test-module {
    yang-version 1.1;

    namespace "org:onap:cps:test:test-module";
    revision "2020-02-02";
    prefix "self";

    import missing-module {
        prefix "missing";
    }

    container self-container {
        uses "missing:missing-group";
    }
}
