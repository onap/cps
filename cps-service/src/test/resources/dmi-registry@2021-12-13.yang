module dmi-registry {

  yang-version 1.1;

  namespace "org:onap:cps:ncmp";

  prefix dmi-reg;

  revision "2021-05-20" {
    description
    "Initial Version";
  }

  revision "2021-12-13" {
    description
    "Added new list of public additonal properties for a Cm-Handle which are exposed to clients of the NCMP interface";
  }

  container dmi-registry {
    list cm-handles {
      key "id";
      leaf id {
        type string;
      }
      leaf dmi-service-name {
        type string;
      }

      list additional-properties {
        key "name";
        leaf name {
          type string;
        }
        leaf value {
          type string;
        }
      }

      list public-properties {
        key "name";
        leaf name {
          type string;
        }
        leaf value {
          type string;
        }
      }
    }
  }
}
