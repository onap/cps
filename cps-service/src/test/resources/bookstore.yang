module stores {
    yang-version 1.1;
    namespace "org:onap:ccsdk:sample";

    prefix book-store;

    revision "2020-09-15" {
        description
        "Sample Model";
    }

    typedef year {
        type uint16 {
            range "1000..9999";
        }
    }

    list bookstore-address {
        key "bookstore-name";
        leaf bookstore-name {
            type string;
            description
            "Name of bookstore. Example: My Bookstore";
        }
        leaf address {
            type string;
            description
            "Address of store";
        }
        leaf postal-code {
            type string;
            description
            "Postal code of store";
        }
    }

    container bookstore {

        leaf bookstore-name {
            type string;
        }

    list categories {

        key "code";

        leaf code {
            type string;
        }

        leaf name {
            type string;
        }

        list books {
            key title;

            leaf title {
                type string;
            }
            leaf lang {
                type string;
            }
            leaf-list authors {
                type string;
            }
            leaf pub_year {
                type year;
            }
            leaf price {
                type uint64;
            }
        }
    }
    }
}
